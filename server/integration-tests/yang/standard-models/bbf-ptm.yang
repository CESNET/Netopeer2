module bbf-ptm {
  yang-version 1.1;

  namespace "urn:bbf:yang:bbf-ptm";

  prefix bbf-ptm;

  import ietf-interfaces {
    prefix if;
  }

  import iana-if-type {
    prefix ianaift;
  }

  organization
    "Broadband Forum <https://www.broadband-forum.org>
     Common YANG Work Area";

  contact
    "Comments or questions about this Broadband Forum YANG module
     should be directed to <mailto:help@broadband-forum.org>.

     Editor:      Joey Boyd, ADTRAN

     Editor:      Ludwig Pauwels, Nokia

     PS Leader:   Joey Boyd, ADTRAN

     PS Leader:   Ken Kerpez, ASSIA

     WA Director: Joey Boyd, ADTRAN

     WA Director: Sven Ooghe, Nokia";

  description
    "This module contains a collection of YANG definitions for 
     supporting the Broadband Forum requirements on interface 
     management as applicable to access network equipment. As such, 
     this module is specific to access network equipment (e.g., 
     BBF-specified Access Nodes and FTTdp DPUs).

     Specifically, this module augments the IETF interfaces data 
     model, ietf-interfaces (RFC7223), with nodes for managing 
     Packet Transfer Mode (PTM) interfaces.

     Copyright (c) 2017-2018, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2018-07-13 {
    description
      "Initial revision.
       * Approval Date:    2018-06-04.
       * Publication Date: see revision date above.";
    reference
      "TR-383: Common YANG Modules
               <https://www.broadband-forum.org/technical/download/
                        TR-383_Amendment-1.pdf>";
  }
  revision 2017-03-13 {
    description
      "Initial revision.
       * Approval Date:    see revision date above.
       * Publication Date: yyyy-mm-dd.";
    reference
      "TR-383: Common YANG Modules
               <https://www.broadband-forum.org/technical/download/
                        TR-383.pdf>";
  }

  augment '/if:interfaces/if:interface' {
    when 'derived-from-or-self(if:type, "ianaift:ptm")' {
      description
        "Common data that defines the relationship between the PTM 
         interface and its lower-layer interface.";
    }

    description
      "Add a reference to a lower-layer interface that is of the type 
       PTM.";

    container ptm {
      description
        "Links the PTM interface to a lower-layer interface.";

      leaf lower-layer-if {
        type if:interface-ref;

        must
          "derived-from-or-self(
           /if:interfaces/if:interface[if:name = current()]
           /if:type,'ianaift:fastdsl')";

        mandatory true;

        description
          "References the lower-layer interface.
           The lower-layer must be of the type fastdsl.";
      }
    }
  }

  grouping ptm-interface-ref {
    description
      "A reference to a PTM interface configuration data.";
    leaf interface {
      type if:interface-ref;

      must
        "derived-from-or-self(/if:interfaces/
         if:interface[if:name = current()]/if:type,
         'ianaift:ptm')" {
        description
          "The referenced interface must be of the type PTM.";
      }

      description
        "A reference to a PTM interface's configuration data.";
    }
  }

  grouping ptm-interface-state-ref {
    description
      "A reference to a PTM interface state data.";
    leaf interface {
      type if:interface-state-ref;

      must
        "derived-from-or-self(/if:interfaces-state/
         if:interface[if:name = current()]/if:type,
         'ianaift:ptm')" {
        description
          "The referenced interface must be of the type PTM.";
      }

      description
        "A reference to a PTM interface's state data.";
    }
  }
}
