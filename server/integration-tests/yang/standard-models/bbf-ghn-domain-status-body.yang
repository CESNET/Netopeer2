submodule bbf-ghn-domain-status-body {
  yang-version 1.1;
  belongs-to bbf-ghn {
    prefix bbf-ghn;
  }

  import bbf-yang-types {
    prefix bbf-yang;
  }

  include bbf-ghn-types;

  organization
    "Broadband Forum <https://www.broadband-forum.org>
     Common YANG Work Area";

  contact
    "Comments or questions about this Broadband Forum YANG module
     should be directed to <mailto:help@broadband-forum.org>.

     Editor:      Marcos Martinez, Marvell Semiconductor Inc.

     PS Leader:   Joey Boyd, ADTRAN

     PS Leader:   Ken Kerpez, ASSIA

     WA Director: Joey Boyd, ADTRAN

     WA Director: Sven Ooghe, Nokia";

  description
    "This module contains a collection of domain status-related
     state data

     Copyright (c) 2018, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-374; see
     the TR itself for full legal notices.";

  revision 2018-07-13 {
    description
      "Initial revision.
       * Approval Date:    2018-06-04.
       * Publication Date: see revision date above.";
    reference
      "TR-374: Yang Modules for Management of G.hn Systems in FTTdp 
               Architecture <https://www.broadband-forum.org/technical
                                     /download/TR-374.pdf>";
  }

  grouping domain-status-parameters {
    description
      "Domain performance parameters.";

    container domain-scheduling {
      description
        "Information related to the domain scheduling.";

      leaf mac-cycle-duration {
        type bbf-ghn:cycle-duration;
        description
          "Medium Access Control (MAC) cycle duration.";
        reference
          "ITU-T G.9961 clause 8.2.2";
      }
    }

    container domain-information {
      description
        "Information related to the domain identification
                and characteristics.";

      leaf domain-name {
        type bbf-ghn:domain-name;
        description
          "The Domain name of the G.hn network the G.hn interface.
           is connected to.";
        reference
          "ITU-T G.9961 clause 8.8.5.2";
      }

      leaf dni {
        type bbf-ghn:dni;
        description
          "The Domain Name Identifier (DNI) of the G.hn 
           network the G.hn interface is connected to.";
        reference
          "ITU-T G.9961 clause 8.6.8.2.1";
      }

      leaf minimum-supported-bandplan {
        type bbf-ghn:bandplan;
        description
          "Minimum bandplan to be able to enter the domain.";
        reference
          "ITU-T G.9961 clause 6";
      }

      leaf maximum-supported-bandplan {
        type bbf-ghn:bandplan;
        description
          "Maximum bandplan to be able to enter the domain.";
        reference
          "ITU-T G.9960 clause 6";
      }
    }

    container domain-topology {
      description
        "Information related to the topology of the domain.";

      leaf topology-update-interval {
        type uint8;
        units "0.1s";
        description
          "Topology update interval for the nodes of a G.hn domain.";
        reference
          "ITU-T G.9961 clause 8.8.5.8.1";
      }
    }

    container security {

      description
        "Container including all security-related status
         information.";

      leaf encryption-enabled {
        type boolean;
        default "true";
        description
          "Defines if the security mechanism is enabled 
           in G.hn links or not.";
        reference
          "ITU-T G.9961 clause 9";
      }


      leaf-list target-domains {

        type bbf-yang:string-ascii64;
        description
          "A list of target domain names for network admission.";
      }
    }
  }
}
