submodule bbf-vdsl-impulse-noise-monitoring-profile-body {
  yang-version 1.1;
  belongs-to bbf-vdsl {
    prefix bbf-vdsl;
  }

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for 
     managing common Broadband Forum TR-252i3 clause 5.7 DSL Quality 
     Management related profiles; INM Profile.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping impulse-noise-monitoring-profile {

    description
      "Impulse Noise Monitoring (INM) is not required for modem
       operation but is a capability for the measurement of Impulse
       Noise. The INM Profile includes the option to control an
       INM function on the receiver of the xTU.";

    leaf inmiato {
      type uint16 {
        range "3..511";
      }
      units "DMT symbols";
      default "3";
      description
        "This is the inter arrival time offset that the xTU
         receiver will use to determine in which bin of the inter
         arrival time histogram the IAT is reported. The valid
         values for INMIATO ranges from 3 to 511 DMT symbols in
         steps of 1 DMT symbol. ";
      reference
        "ITU-T G.997.1 clause 7.3.1.9.1 INM inter arrival time
         offset (INMIATO)";
    }

    leaf inmiats {
      type uint8 {
        range "0..7";
      }
      units "DMT symbols";
      default "0";
      description
        "This is the inter arrival time step that the xTU receiver
         will use to determine in which bin of the inter arrival time
         histogram the IAT is reported. The valid values for INMIATS
         range from 0 to 7 in steps of 1.";
      reference
        "ITU-T G.997.1 clause 7.3.1.9.2 INM inter arrival time
         step (INMIATS)";
    }

    leaf inmcc {
      type uint8 {
        range "0..64";
      }
      units "DMT symbols";
      default "0";
      description
        "This is the cluster continuation value that the xTU
         receiver will use in the cluster indication process
         described in the relevant ITU-T Recommendation. The
         valid values for INMCC range from 0 to 64 DMT symbols in
         steps of one DMT symbol.";
      reference
        "ITU-T G.997.1 clause 7.3.1.9.3 INM cluster continuation
         value (INMCC)";
    }

    leaf inm-inpeq-mode {
      type enumeration {
        enum "0" {
          description
            "INM_INPEQ_MODE = 0 as defined in ITU-T G.993.2
             clause 11.4.2.2.1.";
        }
        enum "1" {
          description
            "INM_INPEQ_MODE = 1 as defined in ITU-T G.993.2
             clause 11.4.2.2.1.";
        }
        enum "2" {
          description
            "INM_INPEQ_MODE = 2 as defined in ITU-T G.993.2
             clause 11.4.2.2.1.";
        }
        enum "3" {
          description
            "INM_INPEQ_MODE = 3 as defined in ITU-T G.993.2
             clause 11.4.2.2.1.";
        }
        enum "4" {
          description
            "INM_INPEQ_MODE = 4 as defined in ITU-T G.993.2
             clause 11.4.2.2.1.";
        }
      }
      default "0";
      description
        "This is the INM equivalent INP mode that the xTU
         receiver will use in the computation of the Equivalent
         INP, as defined in the relevant ITU-T Recommendation. The
         valid values for INM_INPEQ_MODE are 0, 1, 2, 3, and 4.
         The default value is enum 0, corresponding to 
         NM_INPEQ_MODE = 0.";
      reference
        "ITU-T G.997.1 clause 7.3.1.9.4 INM equivalent INP mode
         (INM_INPEQ_MODE)";
    }

    leaf inm-inpeq-format {
      type enumeration {
        enum "0" {
          description
            "Linear scale as defined in ITU-T G.997.1 clause 
             7.3.1.9.5.";
        }
        enum "1" {
          description
            "Logarithmic scale as defined in ITU-T G.997.1 clause 
             7.3.1.9.5.";
        }
      }
      default "0";
      description
        "Defines the way the scale is configured for the INM_INPEQ 
         histogram.";
      reference
        "ITU-T G.993.2 clause 11.4.2.2.6";
    }

    leaf inm-enable {
      type boolean;
      default "false";
      description
        "If true, enables Impulse Noise Monitoring (INM).";
    }
  } // end grouping impulse-noise-monitoring-profile
} // end submodule impulse-noise-monitoring-profile-body
