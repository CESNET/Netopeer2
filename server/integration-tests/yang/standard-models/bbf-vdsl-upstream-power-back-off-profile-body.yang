submodule bbf-vdsl-upstream-power-back-off-profile-body {
  yang-version 1.1;
  belongs-to bbf-vdsl {
    prefix bbf-vdsl;
  }

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for 
     managing Broadband Forum TR-252i3 clause 5.6 Spectrum related
     profiles; UPBO Profile.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping upstream-power-back-off-profile {

    description
      "This configures upstream power back-off (UPBO).";

    leaf upbo-electrical-length {
      type uint16 {
        range "0..1280";
      }
      units "0.1 dB";
      default "0";
      description
        "This parameter defines the electrical length expressed
         in dB at 1 MHz, kl0, configured by the CO MIB. The value
         ranges from 0 to 128 dB in steps of 0.1 dB.";
      reference
        "ITU-T G.997.1 clause 7.3.1.2.14 a.2) Upstream electrical
         length (UPBOKL)";
    }

    leaf upbo-force-electrical-length {
      type boolean;
      default "false";
      description
        "This parameter is a flag that forces the VTU-R to use
         the electrical length of the CO-MIB (UPBOKL) to compute
         the UPBO. The value will be forced if the flag is set to
         true. Otherwise, if false the VTUs will determine the
         electrical length.";
      reference
        "ITU-T G.997.1 clause 7.3.1.2.14 a.3) Force CO-MIB
         electrical length (UPBOKLF)";
    }

    list upbopsd-pb {
      key "band";
      description
        "This parameter defines the UPBO reference PSD used to
         compute the upstream power back-off for each upstream
         band except US0. A UPBOPSD defined for each band will
         consist of two parameters [a, b]. Parameter a ranges
         from 40 dBm/Hz to 80.95 dBm/Hz in steps of 0.01 dBm/Hz;
         and parameter b ranges from 0 to 40.95 dBm/Hz in steps
         of 0.01 dBm/Hz. The UPBO reference PSD at the frequency
         f expressed in MHz will be equal to a bvf. The set of
         parameter values a = 40 dBm/Hz, b = 0 dBm/Hz is a
         special configuration to disable UPBO in the respective
         upstream band.";

      leaf band {
        type uint8 {
          range "0..4";
        }
        description
          "Identifies the upstream band, e.g., a value of 1
           denotes US1";
      }
      leaf upbopsd-a {
        type uint16 {
          range "4000..8095";
        }
        units "0.01 dBm/Hz";
        default "4000";
        description
          "UPBO parameter A";
      }
      leaf upbopsd-b {
        type uint16 {
          range "0..4095";
        }
        units "0.01 dBm/Hz";
        default "0";
        description
          "UPBO parameter B";
      }
      reference
        "ITU-T G.997.1 clause 7.3.1.2.14 a.1) Upstream power
         back-off reference PSD per band (UPBOPSD-pb)";
    }

    list upbo-reference-electrical-length-pb {
      key "band";

      leaf band {
        type uint8 {
          range "0..4";
        }
        description
          "Identifies the upstream band, e.g., a value of 1
           denotes US1";
      }
      leaf upbo-reference-electrical-length {
        type union {
          type uint16 {
            range "18..635";
          }
          type enumeration {
            enum "equalized-fext-upbo-disabled" {
              description
                "Indicates that equalized FEXT UPBO is disabled.";
            }
          }
        }
        units "0.1 dB";
        default "equalized-fext-upbo-disabled";
        description
          "The UPBO reference electrical length.";
      }
      description
        "This parameter defines the UPBO reference electrical
         length used to compute the upstream power back-off for
         each upstream band except US0, for the optional
         Equalized FEXT UPBO method. The value ranges from 1.8 to
         63.5 dB in steps of 0.1 dB. The use
         of the special value (enum equalized-fext-upbo-disabled)
         is described in clause 7.2.1.3.2 of [ITU-T G.993.2] for
         kl0_REF=0.";
      reference
        "ITU-T G.997.1 clause 7.3.1.2.14 a.4) PBO reference
         electrical length per band (UPBOKLREF-pb)";
    }

    leaf aele-mode {
      type enumeration {
        enum "0" {
          description
            "kl0[band] = ELE-M0 VTU-O kl0 estimate";
        }
        enum "1" {
          description
            "kl0[band] = ELEDS [dB], with band in the set
             {upbo_bands}";
        }
        enum "2" {
          description
            "kl0[band] = ELE[band] [dB], with band in the set
             {upbo_bands}";
        }
        enum "3" {
          description
            "kl0[band] = MIN(ELEUS, ELEDS) [dB], with band in the
             set {upbo_bands}";
        }
      }
      default "0";
      description
        "This parameter defines the UPBO electrical length
         estimation mode to be used in the alternative electrical
         length estimation method (ELE-M1) in clause 7.2.1.3.2.2
         of [ITU-T G.993.2]. The value of this parameter is 0, 1,
         2 or 3. The default is enum 0, kl0[band] = 
         ELE-M0 VTU-O kl0 estimate";
      reference
        "ITU-T G.997.1 clause 7.3.1.2.14 a.5) Alternative
         Electrical Length Estimation Mode (AELE-MODE)";
    }

    leaf upbo-elmt {
      type uint8 {
        range "0..15";
      }
      units "1 percent";
      default "0";
      description
        "This parameter defines the UPBO electrical length
         minimum threshold percentile in percent used in the
         alternative electrical length estimation method (ELE-M1)
         in clause 7.2.1.3.2.2 of [ITU-T G.993.2]. It is set by
         network management via the CO-MIB. The parameter ranges
         from 0 to 15 percent in steps of 1 percent. This value
         is communicated to the VTU-R in accordance with [ITU-T
         G.994.1] at start-up.";
      reference
        "ITU-T G.997.1 clause 7.3.1.2.14 a.6) UPBO electrical
         length threshold percentile (UPBOELMT)";
    }
  } // end grouping upstream-power-back-off-profile
} // end submodule upstream-power-back-off-profile-body
