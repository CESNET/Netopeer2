submodule bbf-vdsl-xtu-band-status-body {
  yang-version 1.1;
  belongs-to bbf-vdsl {
    prefix bbf-vdsl;
  }

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for 
     managing Broadband Forum TR-252i3 clause 6.1.1 xTU Band Status.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-band-status {
    description
      "The xTU Band Status object represents current band status
       / measurements at a particular xTU.";

    list line-attenuation {
      key "band";
      description
        "Line attenuation (LATN) per band.";
      leaf band {
        type uint8 {
          range "0..4";
        }
        description
          "Identifies the frequency band. 
           For example, 0 denotes US0.";
      }
      leaf attenuation {
        type union {
          type uint16 {
            range "0..1270";
          }
          type enumeration {
            enum "out-of-range" {
              description
                "Indicates that the line attenuation per band is 
                 out of range to be represented.";
            }
          }
        }
        units "0.1 dB";
        description
          "This parameter is defined per usable band. It is squared
           magnitude of the channel characteristics function H(f)
           averaged over this band, and measured during loop
           diagnostic mode and initialization (LATNds for xTU-R /
           LATNus for xTU-C). The exact definition is included in
           the relevant xDSL ITU-T Recommendation. The line
           attenuation ranges per band from 0 to +127 dB, with 0.1
           dB steps. A special value (enum out-of-range) indicates
           the line attenuation per band is out of range to be
           represented.
           For ADSL systems, a single parameter is defined for 
           band = 0, as only a single band is usable.";
        reference
          "ITU-T G.997.1 clause 7.5.1.9 Downstream line attenuation
           per band (LATNds) and clause 7.5.1.10 Upstream line
           attenuation per band (LATNus)";
      }
    }

    list signal-attenuation {
      key "band";
      description
        "Signal attenuation (SATN) per band.";
      leaf band {
        type uint8 {
          range "0..4";
        }
        description
          "Identifies the frequency band. 
           For example, 0 denotes US0.";
      }
      leaf attenuation {
        type union {
          type uint16 {
            range "0..1270";
          }
          type enumeration {
            enum "out-of-range" {
              description
                "Indicates that the value is out of range
                 to be represented.";
            }
          }
        }
        units "0.1 dB";
        description
          "This parameter is defined per usable band. It is the
           measured difference between the total power transmitted
           in this band and the total power received in this band
           during loop diagnostic mode, initialization and showtime
           (SATNds for xTU-R / SATNus for xTU-C). The exact
           definition is included in the relevant DSL ITU-T
           Recommendation. The signal attenuation per band ranges
           from 0 to +127 dB, with 0.1 dB steps. A special value
           (enum out-of-range) indicates the signal attenuation per
           band is out of range to be represented.
           For ADSL systems, a single parameter is defined for 
           band = 0, as only a single band is usable.";
        reference
          "ITU-T G.997.1 clause 7.5.1.11 Downstream signal
           attenuation per band (SATNds) and clause 7.5.1.12
           Upstream signal attenuation per band (SATNus)";
      }
    }

    list snr-margin {
      key "band";
      description
        "SNR margin per band.";
      leaf band {
        type uint8 {
          range "0..4";
        }
        description
          "Identifies the frequency band. 
           For example, 0 denotes US0.";
      }
      leaf margin {
        type union {
          type int16 {
            range "-640..630";
          }
          type enumeration {
            enum "out-of-range" {
              description
                "Indicates that the value is out of range to
                 be represented.";
            }
          }
        }
        units "0.1 dB";
        description
          "This parameter is defined per usable band. The
           signal-to-noise ratio margin per band is the maximum
           increase in dB of the received noise power, such that
           the BER requirements are met for all bearer channels in
           the direction of transmission (SNRMpbds for xTU-R /
           SNRMpbus for xTU-C). The SNR margin per band ranges from
           -64 dB to +63 dB, with 0.1 dB steps. A special value
           (enum out-of-range) indicates the parameter is out of 
           range to be represented. 
           For ADSL systems, a single parameter is defined for 
           band = 0, as a single band is usable.";
        reference
          "ITU-T G.997.1 clause 7.5.1.14 Downstream signal-to-noise
           ratio margin per band (SNRMpbds) and clause 7.5.1.17
           Upstream signal-to-noise ratio margin per band
           (SNRMpbus)";
      }
    }

    list upbo-electrical-length-pbn {
      key "band";
      description
        "Upstream power backoff (UPBO) electrical length
         per band.";
      leaf band {
        type uint8 {
          range "0..4";
        }
        description
          "Identifies the frequency band. 
           For example, 0 denotes US0.";
      }
      leaf upbo-electrical-length {
        type union {
          type uint16 {
            range "0..1280";
          }
          type enumeration {
            enum "out-of-range" {
              description
                "Indicates that the estimate is greater than
                 128 dB.";
            }
          }
        }
        units "0.1 dB";
        description
          "This parameter is a vector of UPBO electrical length
           per-band estimates for each supported upstream band,
           expressed in dB at 1 MHz (kl0) calculated by the VTU
           (UPBOKLE-pb for the VTU-O, UPBOKLE-r-pb for the VTU-R),
           based on separate measurements in the supported upstream
           bands excluding US0. The value ranges from 0 to 128 dB
           in steps of 0.1 dB, with special value 
           (enum out-of-range) which indicates that the estimate is
           greater than 128 dB. This parameter is needed for the
           alternative electrical length estimation method (ELE-M1).";
        reference
          "ITU-T G.997.1 clause 7.5.1.23.3 VTU-O estimated upstream
           power back-off electrical length per band (UPBOKLE-pb)
           and clause 7.5.1.23.4 VTU-R estimated upstream power
           back-off electrical length per band (UPBOKLE-R-pb)";
      }
    }
  } // end grouping xtu-band-status
} // end submodule xtu-band-status-body
