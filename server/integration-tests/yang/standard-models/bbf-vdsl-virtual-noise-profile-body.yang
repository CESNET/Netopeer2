submodule bbf-vdsl-virtual-noise-profile-body {
  yang-version 1.1;
  belongs-to bbf-vdsl {
    prefix bbf-vdsl;
  }

  include bbf-vdsl-base-body;

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for 
     managing Broadband Forum TR-252i3 5.7 DSL Quality Management 
     related profiles; Virtual Noise Profile.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping vn-descriptor {
    description
      "Specifies the format of the Virtual Noise (VN) PSD.";
    list psdmask {
      key "sub-carrier";
      leaf sub-carrier {
        type sub-carrier-index;
        description
          "Sub-carrier index";
      }

      leaf psd-level {
        type union {
          type uint8 {
            range "0..200";
          }
          type enumeration {
            enum "zero-watts-per-hz" {
              description
                "Indicates a noise level of 0 W/Hz 
                 (minus infinity dBm/Hz).";
            }
          }
        }
        units "-0.5 dBm/Hz";
        mandatory true;
        description
          "The noise level, ranges from -40 dBm/Hz to -140 dBm/Hz
           in steps of -0.5 dBm/Hz, with an offset of -40 dBm/Hz.
           The virtual noise level = -psd-level/2 -40 dBm/Hz.
           A special value of (enum zero-watts-per-hz) indicates
           a noise level of 0 W/Hz (minus infinity dBm/Hz). 
           The default is an empty list, corresponding to no
           virtual noise defined.";
      }
      description
        "The virtual noise PSD level.";
    }
  }


  grouping virtual-noise-profile {

    description
      "Configuration parameters for downstream Virtual Noise (VN).";
    container virtual-noise {
      must "count(psdmask) != 1" {
        description
          "There must be either 0 or 2 to 32 PSD masks defined.";
      }
      uses vn-descriptor {
        refine "psdmask" {
          max-elements 32;
        }
      }
      description
        "This configuration parameter VN defines the transmitter
         referred virtual noise (TXREFVN). The TXREFVN is
         specified through a set of breakpoints. Each breakpoint
         consists of a subcarrier index t, with a subcarrier
         spacing of 4.3125 kHz, and a noise PSD level (expressed
         in dBm/Hz) at that subcarrier. The set of breakpoints
         can then be represented as [(t1, PSD1), (t2, PSD2), ,
         (tN, PSDN)]. The subcarrier index is coded as an
         unsigned integer. The noise level ranges from -40 dBm/Hz
         to -140 dBm/Hz in steps of 0.5 dBm/Hz. A special value
         of (enum zero-watts-per-hz) indicates a noise level of
         0 W/Hz. The maximum number of breakpoints is 32.
         The default is an empty list, corresponding to no virtual
         noise defined.";
      reference
        "ITU-T G.997.1 clause 7.3.1.7.3 Downstream Virtual noise
         (VNds).";
    }

    container fext-txrefvnds {
      uses vn-descriptor;
      description
        "For ITU-T G.992.3 (ADSL2) Annex C and ITU-T G.992.5
         (ADSL2plus) Annex C, the transmitter referred virtual
         noise (see clause 7.3.1.7.3) specified for FEXTR
         duration is defined as FEXT downstream transmitter
         referred virtual noise (FEXT TXREFVNds). The default is
         an empty list, corresponding to no virtual noise defined.";
      reference
        "ITU-T G.997.1 clause 7.3.1.7.3.1 FEXT downstream
         transmitter referred virtual noise (FEXT TXREFVNds)";
    }

    container next-txrefvnds {
      uses vn-descriptor;
      description
        "For ITU-T G.992.3 (ADSL2) Annex C and ITU-T G.992.5
         (ADSL2plus) Annex C, the transmitter referred virtual
         noise (see clause 7.3.1.7.3) specified for NEXTR
         duration is defined as NEXT downstream transmitter
         referred virtual noise (NEXT TXREFVNds). The default is
         an empty list, corresponding to no virtual noise defined.";
      reference
        "ITU-T G.997.1 clause 7.3.1.7.3.2 NEXT downstream
         transmitter referred virtual noise (NEXT TXREFVNds)";
    }

    leaf txrefvnsfds {
      type int8 {
        range "-128..127";
      }
      units "0.5 dB";
      default "0";
      description
        "If SNRM_MODE = 4, this configuration parameter defines
         the downstream transmitter referred virtual noise
         scaling factor. The valid values for the transmitter
         referred virtual noise scaling factor range from -64.0
         dB to 63.5 dB, in steps of 0.5 dB. The default is
         an empty list, corresponding to no virtual noise defined.";
      reference
        "ITU-T G.997.1 clause 7.3.1.7.6 Downstream virtual noise
         scaling factor (TXREFVNSFds)";
    }
  } // end grouping virtual-noise-profile (~downstream)

  grouping virtual-noise-profile-upstream {

    description
      "Configuration parameters for upstream Virtual Noise (VN).";

    container virtual-noise {
      must "count(psdmask) != 1" {
        description
          "There must be either 0 or 2 to 16 PSD masks defined.";
      }
      uses vn-descriptor {
        refine "psdmask" {
          max-elements 16;
        }
      }
      description
        "This configuration parameter VN defines the transmitter
         referred virtual noise (TXREFVN). The TXREFVN is
         specified through a set of breakpoints. Each breakpoint
         consists of a subcarrier index t, with a subcarrier
         spacing of 4.3125 kHz, and a noise PSD level (expressed
         in dBm/Hz) at that subcarrier. The set of breakpoints
         can then be represented as [(t1, PSD1), (t2, PSD2), ,
         (tN, PSDN)]. The subcarrier index is coded as an
         unsigned integer. The noise level ranges from -40 dBm/Hz
         to -140 dBm/Hz in steps of 0.5 dBm/Hz. A special value
         of (enum zero-watts-per-hz) indicates a noise level of
         0 W/Hz. The maximum number of breakpoints is 16.
         The default is an empty list, corresponding to no virtual
         noise defined.";
      reference
        "ITU-T G.997.1 clause 7.3.1.7.4 Upstream virtual noise
         (VNus).";
    }

    leaf rxrefvnsfus {
      type int8 {
        range "-128..127";
      }
      units "0.5 dB";
      default "0";
      description
        "If SNRM_MODE = 4, this configuration parameter defines
         the receiver-referred virtual noise scaling factor. The
         valid values for the receiver-referred virtual noise
         scaling factor range from -64.0 dB to 63.5 dB, in steps
         of 0.5 dB. The default is
         an empty list, corresponding to no virtual noise defined.";
      reference
        "ITU-T G.997.1 clause 7.3.1.7.5 Upstream virtual noise
         scaling factor (RXREFVNSFus)";
    }
  } // end grouping virtual-noise-profile-upstream
} // end submodule virtual-noise-profile-body
