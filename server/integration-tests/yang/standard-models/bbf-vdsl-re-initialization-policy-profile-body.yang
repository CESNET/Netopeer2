submodule bbf-vdsl-re-initialization-policy-profile-body {
  yang-version 1.1;
  belongs-to bbf-vdsl {
    prefix bbf-vdsl;
  }

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for 
     managing Broadband Forum TR-252i3 clause 5.7 DSL Quality 
     Management related profiles; Re-initialization Policy Profile.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping re-initialization-policy-profile {

    description
      "Configuration of the re-initialization policy allows control
       of re-initialization based on error performance thresholds
       of the line.";

    leaf ripolicy {
      type uint8 {
        range "0..1";
      }
      default "0";
      description
        "The RIPOLICY parameter indicates which policy will be
         applied to determine the triggers for re-initialization
         in the direction of transmisson (see clause 12.1.4 of
         [ITU-T G.993.2] and clauses 7.3.1.1.13 and 7.2.1.1.5 of
         [ITU-T G.997.1]).
         If RIPOLICY=1 is configured and it is detected during
         ITU-T G.993.2 initialization that RIPOLICY=1 is not
         supported in the direction of transmission by either of
         the XTUs, the XTUs will fallback to RIPOLICY=0. The
         valid values for RIPOLICY are 0 and 1.
         The default is RIPOLICY=0.";
      reference
        "ITU-T G.997.1 clause 7.3.1.1.12.1 Downstream
         re-initialization policy selection (RIPOLICYds) and
         clause 7.3.1.1.12.2 Upstream re-initialization policy
         selection (RIPOLICYus)";
    }

    leaf reinit-time-threshold {
      type uint8 {
        range "5..31";
      }
      default "10";
      description
        "The parameter REINIT_TIME_THRESHOLD defines the
         threshold for re-initialization based on SES, to be used
         by the VTU receiver when re-initialization policy 1 is
         used in the direction of transmission (see clause 12.1.4
         of [ITU-T G.993.2]). The valid range is from 5 to 31.";
      reference
        "ITU-T G.997.1 clause 7.3.1.1.13.1 Downstream
         REINIT_TIME_THRESHOLDds and clause 7.3.1.1.13.2 Upstream
         REINIT_TIME_THRESHOLDus";
    }
  } // end grouping re-initialization-policy-profile
} // end submodule re-initialization-policy-body
