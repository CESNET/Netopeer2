module bbf-l2-dhcpv4-relay-forwarding {
  yang-version 1.1;
  namespace "urn:bbf:yang:bbf-l2-dhcpv4-relay-forwarding";

  prefix bbf-l2-d4r-fwd;

  import bbf-l2-forwarding {
    prefix bbf-l2-fwd;
  }

  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "This module contains a collection of YANG definitions for 
     supporting the Broadband Forum requirements on subscriber 
     management via the DHCPv4 protocol as applicable to access 
     network equipment. As such, this module is specific to access 
     network equipment (e.g., BBF-specified Access Nodes and FTTdp 
     DPUs).

     Specifically, this module augments bbf-l2-forwarding with 
     subscriber management via the DHCPv4 protocol.

     Copyright (c) 2017, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2017-05-08 {
    description
      "Initial revision.
       * Approval Date:    see revision date above.
       * Publication Date: 2017-06-02.";
    reference
      "TR-383: Common YANG Modules
               <https://www.broadband-forum.org/technical/download/
                        TR-383.pdf>";
  }

  augment '/bbf-l2-fwd:forwarding/bbf-l2-fwd:forwarders/bbf-l2-fwd:'
        + 'forwarder' {
    description
      "Additions for L2 DHCPv4 Relay Agent at the forwarder level.";

    container l2-dhcpv4-relay {
      description
        "L2 DHCPv4 Relay Agent related controls.";

      leaf downstream-broadcast-flooding {
        type boolean;
        default "false";
        description
          "If it is configured as 'true', the L2 DHCP Relay Agent will
           flood downstream broadcast 'DHCPv4 packets' to all output 
           ports of the forwarder; if it is configured as 'false', the
           L2 DHCP Relay Agent will forward downstream 'broadcast 
           DHCPv4 packets' to only one port of the forwarder, i.e. the
           one for which the packet is intended. Identifying the port 
           for which the packet is intended is based on packet 
           content.";
      }
    }
  }
}
