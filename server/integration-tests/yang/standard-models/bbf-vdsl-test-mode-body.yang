submodule bbf-vdsl-test-mode-body {
  yang-version 1.1;
  belongs-to bbf-vdsl {
    prefix bbf-vdsl;
  }

  include bbf-vdsl-base-body;

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for 
     managing Broadband Forum TR-252i3 clause 5.1 xDSL Line.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping test-mode {

    description
      "The object contains parameters that invoke test modes and 
       update test parameters.";

    container test-mode {
      description
        "update test parameters";

      leaf power-management-state-forced {
        type enumeration {
          enum "0" {
            description
              "Force the line to transition from the L3 idle state
               to the L0 full-on state (i.e., both xTUs are in
               showtime). This transition requires the (short or
               full) initialization procedures. After reaching the
               L0 state, the line may transition into or exit from
               the L2 low power state (if L2 state is defined and
               enabled). If the L0 state is not reached (after a
               vendor discretionary number of retries and/or within
               a vendor discretionary timeout), then an
               Initialization failure occurs. Whenever the line is
               in the L3 state, attempts will be made to transition
               to the L0 state until it is forced into another state
               through this configuration parameter.";
          }
          enum "2" {
            description
              "Force the line to transition from L0 full on to L2
               low power state. This transition requires the entry
               into L2 mode. This is an out-of-service test value
               for triggering the L2 mode and is valid only for
               Recommendations supporting L2 mode.
               This parameter value is only applicable for operation
               according to G.992.3, G.992.4 or G.992.5. If not
               applicable, this value is ignored until its use is
               defined.";
          }
          enum "3" {
            description
              "Force the line to transition from the L0 full-on or 
               L2 low power state to the L3 idle state. This
               transition requires the (orderly) shutdown procedure.
               After reaching the L3 state, the line will remain in
               the L3 idle state until it is forced into another
               state through this configuration parameter.";
          }
          enum "4" {
            description
              "No power management state forced.";
          }
        }
        default "4";
        description
          "This configuration parameter defines the line states to
           be forced by the near-end xTU on this line.
           The default is enum 4, no power management state forced.";
        reference
          "ITU-T G.997.1 7.3.1.1.3 Power management state forced
           (PMSF)";
      }

      leaf loop-diagnostics-mode-forced {
        type enumeration {
          enum "0" {
            description
              "Inhibits the near-end xTU from performing loop
               diagnostic mode procedures on the line. Loop 
               diagnostic mode procedures may still be initiated
               by the far-end xTU.";
          }
          enum "1" {
            description
              "Forces the near-end xTU to perform the loop
               diagnostic procedures.";
          }
          enum "2" {
            description
              "No loop diagnostic mode forced.";
          }
        }
        default "2";
        description
          "This configuration parameter defines whether the line
           should be forced into the loop diagnostic mode by the
           near-end xTU on this line. The default is no loop 
           diagnostic mode forced, corresponding to enum 2.";
        reference
          "ITU-T G.997.1 clause 7.3.1.1.8 Loop diagnostic mode
           forced (LDSF)";
      }

      leaf auto-mode-cold-start-forced {
        type uint8 {
          range "0..1";
        }
        description
          "This parameter is defined in order to improve testing of
           the performance of xTUs supporting automode when it is
           enabled in the MIB. The valid values are 0 and 1. A
           change in value of this parameter indicates a change in
           loop conditions applied to the devices under test. The
           xTUs will reset any historical information used for
           automode, for shortening G.994.1 handshake, or for
           shortening the initialization procedure.
           The default is no automode cold start forced.";
        reference
          "ITU-T G.997.1 clause 7.3.1.1.10 Automode cold start
           forced";
      }
    }
  } // end grouping test-mode

  grouping update-test {
    description
      "This is defined so that test parameters can be forced to
       be updated.";

    container xtu-c {
      description
        "The update-test-ne is performed on the xtu-c.";
      leaf update-test-ne {
        type uint8 {
          range "0..1";
        }
        default "0";
        description
          "This parameter is defined to force an update of the
           near-end test parameters that can be updated during
           showtime. The parameter is configurable over the
           Q-interface and the valid values are 0 and 1. When this
           parameter is set (its value is changed from 0 to 1), the
           near-end test parameters will be updated in the AN MIB
           within 10 seconds. The update request flag for the
           near-end test parameters is defined in the AN MIB and is
           independent of any autonomous update process in the
           system. The parameter will be reset (its value changed
           back to 0) by the AN after a period shorter than 3
           minutes to allow reception of another update request.
           The 3-minute period starts since the last time the flag
           was set (externally or by an autonomous process in the
           system). This applies only to the elements maintained in
           the AN.";
        reference
          "ITU-T G.997.1 clause 7.5.1.36.1 Update request flag for
           near-end test parameters (UPDATE-TEST-NE)";
      }

      leaf xlin-disturber-vce-port-index-ds {
        type vce-port-index;
        default "undefined";
        description
          "The requested XLIN downstream disturber VCE port index.";
      }

      leaf xlin-disturber-vce-port-index-us {
        type vce-port-index;
        default "undefined";
        description
          "The requested XLIN upstream disturber VCE port index.";
      }
    }

    container xtu-r {
      description
        "The update-test-fe is performed on the xtu-r.";
      leaf update-test-fe {
        type uint8 {
          range "0..1";
        }
        default "0";
        description
          "This parameter is defined to force an update of the
           far-end test parameters that can be updated during
           showtime. The parameter is configurable over the
           Q-interface and the valid values are 0 and 1. When this
           parameter is set (its value is changed from 0 to 1), the
           far-end test parameters will be updated in the AN MIB
           within 30 seconds. The update request flag for the
           far-end test parameters is defined in the AN MIB and is
           independent of any autonomous update process in the
           system. The parameter will be reset (its value changed
           back to 0) by the AN after a period shorter than 3
           minutes to allow reception of another update request.
           The 3-minute period starts since the last time the flag
           was set (externally or by an autonomous process in the
           system). This applies only to the elements maintained in
           the AN.";
        reference
          "ITU-T G.997.1 clause 7.5.1.36.2 Update request flag for
           far-end test parameters (UPDATE-TEST-FE)";
      }
    }
  } // end grouping update-test
} // end submodule bbf-vdsl-test-mode-body
