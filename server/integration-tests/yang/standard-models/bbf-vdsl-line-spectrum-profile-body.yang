submodule bbf-vdsl-line-spectrum-profile-body {
  yang-version 1.1;
  belongs-to bbf-vdsl {
    prefix bbf-vdsl;
  }

  include bbf-vdsl-base-body;
  include bbf-vdsl-mode-specific-psd-profile-body;

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for 
     managing Broadband Forum TR-252i3 clause 5.6 Spectrum related
     profiles; Line Spectrum Profile.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping sub-carrier-range {
    description
      "Defines a sub-carrier band, i.e., a set of contigious
       sub-carriers.";

    leaf start-index {
      type sub-carrier-index;
      must ". <= ../stop-index" {
        description
          "The start index must be less than or equal to the stop
           index";
      }
      mandatory true;
      description
        "The sub-carrier index identifying the start of a range of
         sub-carriers (inclusive).";
    }

    leaf stop-index {
      type sub-carrier-index;
      must ". >= ../start-index" {
        description
          "The stop index must be greater than or equal to the
           start index";
      }
      mandatory true;
      description
        "The sub-carrier index identifying the stop of a range of
         sub-carriers (inclusive).";
    }
  }

  grouping line-spectrum-profile {

    description
      "The Line Spectrum Profile contains the parameters that are
       mainly set during the service delivery phase.";

    leaf power-management-mode {
      type union {
        type enumeration {
          enum "all" {
            description
              "All power management modes enabled.";
          }
        }
        type bits {
          bit bit0 {
            position 0;
            description
              "L3 state (idle state)";
          }
          bit bit1 {
            position 1;
            description
              "L1/L2 state (low power state)";
          }
        }
      }
      default "all";
      description
        "This configuration parameter defines the line states the
         xTU-C or xTU-R may autonomously transition to on this
         line. It is coded in a bit-map representation
         (0 if not allowed, 1 if allowed).
         The default is 'all', corresponding to all power management 
         states allowed.";
      reference
        "ITU-T G.997.1 clause 7.3.1.1.4 Power management state
         enabling (PMMode).";
    }

    leaf l0-minimum-time {
      type uint8 {
        range "0..255";
      }
      units "seconds";
      default "127";
      description
        "This parameter represents the minimum time (in seconds)
         between an exit from the L2 state and the next entry
         into the L2 state. It ranges from 0 to 255 seconds.";
      reference
        "ITU-T G.997.1 clause 7.3.1.1.5 Minimum L0 time interval
         between L2 exit and next L2 entry (L0-TIME)";
    }

    leaf l2-minimum-time {
      type uint8 {
        range "0..255";
      }
      units "seconds";
      default "127";
      description
        "This parameter represents the minimum time (in seconds)
         between an entry into the L2 state and the first power
         trim in the L2 state and between two consecutive power
         trims in the L2 state. It ranges from 0 to 255
         seconds.";
      reference
        "ITU-T G.997.1 clause 7.3.1.1.6 Minimum L2 time interval
         between L2 entry and first L2 trim (L2-TIME)";
    }

    leaf l2-maximum-aggregate-power-reduction-per {
      type uint8 {
        range "0..31";
      }
      units "1 dB";
      must ". <= ../l2-maximum-aggregate-power-reduction-total" {
        description
          "The maximum aggregate transmit power reduction per L2 
           request or power trim must be less than or equal to the
           maximum aggregate transmit power reduction that can be
           performed in an L2 state.";
      }
      default "1";
      description
        "This parameter represents the maximum aggregate transmit
         power reduction (in dB) that can be performed in the L2
         request (i.e., at transition of L0 to L2 state) or
         through a single power trim in the L2 state. It ranges
         from 0 dB to 31 dB in steps of 1 dB.";
      reference
        "ITU-T G.997.1 clause 7.3.1.1.7 Maximum aggregate
         transmit power reduction per L2 request or L2 power trim
         (L2-ATPR)";
    }

    leaf l2-maximum-aggregate-power-reduction-total {
      type uint8 {
        range "0..31";
      }
      units "1 dB";
      default "10";
      description
        "This parameter represents the total maximum aggregate
         transmit power reduction (in dB) that can be performed
         in an L2 state. This is the sum of all reductions of L2
         Request (i.e., at transition of L0 to L2 state) and
         power trims. It ranges from 0 dB to 31 dB in steps of 1
         dB.";
      reference
        "ITU-T G.997.1 clause 7.3.1.1.9 Total maximum aggregate
         transmit power reduction in L2 (L2-ATPRT)";
    }

    leaf-list carmaskds {
      type uint16 {
        range "0..511";
      }
      description
        "This configuration parameter is a list of sub-carriers which
         are masked on this line in the downstream direction ranging
         from 0 to the highest supported sub-carrier index-1.
         For [ITU-T G.992.3], [ITU-T G.992.4], and [ITU-T G.992.5],
         the highest sub-carrier index is defined in the
         corresponding Recommendations.
         For [ITU-T G.992.1], the highest sub-carrier index = 256 and
         for [ITU-T G.992.2], the highest sub-carrier index = 128.
         If no elements exist, there are no masked sub-carriers.";
      reference
        "ITU-T G.997.1 clause 7.3.1.2.6 Downstream subcarrier
         masking (CARMASKds)";
    }

    leaf-list carmaskus {
      type uint16 {
        range "0..63";
      }
      description
        "This configuration parameter is a list of sub-carriers which
         are masked on this line in the upstream direction ranging
         from 0 to the highest supported sub-carrier index-1.
         For [ITU-T G.992.3], [ITU-T G.992.4], and [ITU-T G.992.5],
         the highest sub-carrier index is defined in the
         corresponding Recommendations.
         For Annex A of [ITU-T G.992.1] and [ITU-T G.992.2],
         the highest sub-carrier index = 32 and
         for Annex B of [ITU-T G.992.1], the highest sub-carrier
         index = 64. If no elements exist, there are no masked 
         sub-carriers.";
      reference
        "ITU-T G.997.1 clause 7.3.1.2.7 Upstream subcarrier
         masking (CARMASKus)";
    }

    list vdsl2-carmask {
      key "start-index";
      max-elements 16;
      uses sub-carrier-range;
      description
        "This configuration parameter defines the restrictions,
         additional to the band plan, to determine the set of
         subcarriers allowed for transmission in both upstream
         and downstream directions.

         The VDSL2-CARMASK will describe the not masked
         subcarriers as one or more frequency bands. Each band is
         represented by start and stop subcarrier indices with a
         subcarrier spacing of 4.3125 kHz. The valid range of
         subcarrier indices specifying the VDSL2-CARMASK is from
         to at least the index of the highest allowed
         subcarrier in both transmission directions among all
         profiles enabled by the parameter PROFILES (see clause
         7.3.1.1.11 of ITU-T G.997.1).

         Up to 16 bands may be specified. Other subcarriers will be 
         masked.

         For profiles using 8.625 kHz tone spacing, the odd
         subcarrier indices i4.3125 in VDSL2-CARMASK will be
         transformed into actual subcarrier indices i8.625 using
         the following rule:
           - for the start frequency of each band:
               i8.625 = (i4.3125 + 1)/2
           - for the stop frequency of each band:
               i8.625 = (i4.3125 - 1)/2.

         The default is an empty list indicating no masked 
         sub-carriers.";
      reference
        "ITU-T G.997.1 clause 7.3.1.2.8 VDSL2 subcarrier masking
         (VDSL2-CARMASK)";
    }

    leaf msgminds {
      type uint8 {
        range "4..248";
      }
      units "1000 bit/s";
      default "16";
      description
        "This parameter defines the minimum rate of the message
         based overhead that will be maintained by the xTU in the
         downstream direction. MSGMINds is expressed in bits per
         second and ranges from 4,000 to 248,000 bit/s with 1,000
         bit/s steps. Valid values are specified in the relevant
         ITU-T Recommendation, e.g., [ITU-T G.992.3] and [ITU-T
         G.993.2].";
      reference
        "ITU-T G.997.1 clause 7.3.1.5.2 Minimum overhead rate
         downstream (MSGMINds)";
    }

    leaf msgminus {
      type uint8 {
        range "4..248";
      }
      units "1000 bit/s";
      default "16";
      description
        "This parameter defines the minimum rate of the message
         based overhead that will be maintained by the xTU in the
         upstream direction. MSGMINus is expressed in bits per
         second and ranges from 4,000 to 248,000 bit/s with 1,000
         bit/s steps. Valid values are specified in the relevant
         ITU-T Recommendation, e.g., [ITU-T G.992.3] and [ITU-T
         G.993.2].";
      reference
        "ITU-T G.997.1 clause 7.3.1.5.1 Minimum overhead rate
         upstream (MSGMINus)";
    }

    leaf profiles {
      type union {
        type enumeration {
          enum "all" {
            description
              "Used to indicate that all profiles are allowed.";
          }
        }
        type profiles;
      }
      default "all";
      description
        "This configuration parameter contains the ITU-T G.993.2
         profiles to be allowed by the near-end xTU on this line.
         It is coded as a list of profiles or the special value 'all'.
         The default is 'all', corresponding to all profiles 
         allowed.";
      reference
        "ITU-T G.997.1 clause 7.3.1.1.11 VDSL2 profiles enabling
         (PROFILES)";
    }

    leaf us0mask {
      type us0mask-descriptor;
      default "all";
      description
        "This parameter contains the US0 PSD masks to be allowed
         by the near-end xTU on the line.
         The default is 'all', corresponding to all US0 PSD masks
         allowed.

         This parameter only applies to [ITU-T G.993.2 Annex A].";
    }

    leaf cyclic-extension-flag {
      type boolean;
      default "false";
      description
        "This parameter is a bit that enables the use of the
         optional cyclic extension values. If the value is set to
         true, the optional cyclic extension values may be
         used. Otherwise, the cyclic extension will be forced to
         the mandatory length (5N/32).";
      reference
        "ITU-T G.997.1 clause 7.3.1.6.1 Optional cyclic extension
         flag (CEFLAG)";
    }

    leaf rtx-mode-ds {
      type enumeration {
        enum "0" {
          description
            "RTX_FORBIDDEN: ITU-T G.998.4 retransmission not
             allowed.";
        }
        enum "1" {
          description
            "RTX_PREFERRED: ITU-T G.998.4 retransmission is
             preferred by the operator (i.e., if ITU-T G.998.4
             RTX capability is supported by both XTUs, the XTUs
             will select ITU-T G.998.4 operation for this
             direction).";
        }
        enum "2" {
          description
            "RTX_FORCED: Force the use of the ITU-T G.998.4
             retransmission (i.e., if ITU-T G.998.4 RTX
             capability in this direction is not supported by
             both XTUs or not selected by the XTUs, an
             initialization failure will result).";
        }
        enum "3" {
          description
            "RTX_TESTMODE: Force the use of the ITU-T G.998.4
             retransmission in test mode (i.e., if ITU-T G.998.4
             RTX capability is not supported by both XTUs or not
             selected by the XTUs, an initialization failure will
             result).";
        }
      }
      default "1";
      description
        "This parameter controls the mode of operation of [ITU-T
         G.998.4] retransmission in the downstream direction. In
         [ITU-T G.992.3] and [ITU-T G.992.5] only the downstream
         parameter RTX_MODE_ds is relevant, the value in the
         upstream direction will be ignored. In [ITU-T G.993.2],
         both parameters are relevant. This parameter has 4 valid
         values. The default value is enum 1, corresponding to
         RTX_PREFERRED";
      reference
        "ITU-T G.997.1 clause 7.3.1.11 Retransmission mode
         (RTX_MODE_ds)";
    }

    leaf rtx-mode-us {
      type enumeration {
        enum "0" {
          description
            "RTX_FORBIDDEN: ITU-T G.998.4 retransmission not
             allowed.";
        }
        enum "1" {
          description
            "RTX_PREFERRED: ITU-T G.998.4 retransmission is
             preferred by the operator (i.e., if ITU-T G.998.4
             RTX capability is supported by both XTUs, the XTUs
             will select ITU-T G.998.4 operation for this
             direction).";
        }
        enum "2" {
          description
            "RTX_FORCED: Force the use of the ITU-T G.998.4
             retransmission (i.e., if ITU-T G.998.4 RTX
             capability in this direction is not supported by
             both XTUs or not selected by the XTUs, an
             initialization failure will result).";
        }
        enum "3" {
          description
            "RTX_TESTMODE: Force the use of the ITU-T G.998.4
             retransmission in test mode (i.e., if ITU-T G.998.4
             RTX capability is not supported by both XTUs or not
             selected by the XTUs, an initialization failure will
             result).";
        }
      }
      default "1";
      description
        "This parameter controls the mode of operation of [ITU-T
         G.998.4] retransmission in the upstream direction. In
         [ITU-T G.992.3] and [ITU-T G.992.5] only the downstream
         parameter RTX_MODE_ds is relevant, the value in the
         upstream direction will be ignored. In [ITU-T G.993.2],
         both parameters are relevant. This parameter has 4 valid
         values. The default value is enum 1, corresponding to
         RTX_PREFERRED.
         NOTE - Due to the optionality of ITU-T G.998.4
         retransmission in upstream direction, the use of
         RTX_FORCED in upstream may lead to initialization
         failure, even if the XTU is supporting ITU-T G.998.4 (in
         downstream).";
      reference
        "ITU-T G.997.1 clause 7.3.1.11 Retransmission mode
         (RTX_MODE_us)";
    }
  } // end grouping line-spectrum-profile
} // end submodule line-spectrum-profile-body
