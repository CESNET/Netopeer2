module bbf-qos-filters {
  yang-version 1.1;
  namespace "urn:bbf:yang:bbf-qos-filters";

  prefix bbf-qos-filt;

  import bbf-yang-types {
    prefix bbf-yang;
  }

  import bbf-qos-classifiers {
    prefix bbf-qos-cls;
  }

  import bbf-frame-classification {
    prefix bbf-classif;
  }

  organization
    "Broadband Forum <https://www.broadband-forum.org>
     Common YANG Work Area";

  contact
    "Comments or questions about this Broadband Forum YANG module
     should be directed to <mailto:help@broadband-forum.org>.

     Editor:      Joey Boyd, ADTRAN

     Editor:      Ludwig Pauwels, Nokia

     PS Leader:   Joey Boyd, ADTRAN

     PS Leader:   Ken Kerpez, ASSIA

     WA Director: Joey Boyd, ADTRAN

     WA Director: Sven Ooghe, Nokia";

  description
    "This module contains a collection of YANG definitions for 
     supporting the Broadband Forum requirements on the management of
     Quality of Service (QoS) as applicable to access network 
     equipment. As such, this module is specific to access network 
     equipment (e.g., BBF-specified Access Nodes and FTTdp DPUs).

     Specifically, this module contains definitions of filter 
     criteria.

     Copyright (c) 2017-2018, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2018-07-13 {
    description
      "Initial revision.
       * Approval Date:    2018-06-04.
       * Publication Date: see revision date above.";
    reference
      "TR-383: Common YANG Modules
               <https://www.broadband-forum.org/technical/download/
                        TR-383_Amendment-1.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  container filters {
    description
      "Filters configuration.";

    list filter {
      key "name";
      description
        "List of filter entries.";

      leaf name {
        type bbf-yang:string-ascii64;
        description
          "Filter name.";
      }

      leaf description {
        type bbf-yang:string-ascii64-or-empty;
        description
          "Description of the class template.";
      }

      leaf filter-match {
        type boolean;
        default "true";
        description
          "This is logical operator for a filter. 
           When true, it indicates the filter looks for a match with
           a pattern defined by the filter-field. When false, it looks
           for a 'no match' with the pattern defined by the filter 
           field.";
      }

      choice filter-field {
        description
          "A field to be classified.";

        case source-mac-address {
          container source-mac-address {
            uses bbf-classif:mac-address-match;
            description
              "Filter containing source MAC address.";
          }
        }

        case destination-mac-address {
          container destination-mac-address {
            uses bbf-classif:mac-address-match;
            description
              "Filter containing destination MAC address.";
          }
        }
      }
    }
  }

  grouping filter-entry-ref {
    description
      "A reference to a filter.";

    leaf filter-name {
      type leafref {
        path '/bbf-qos-filt:filters/bbf-qos-filt:filter/bbf-qos-'
           + 'filt:name';
      }
      description
        "A reference to a filter.";
    }
  }


  augment '/bbf-qos-cls:classifiers/bbf-qos-cls:classifier-entry/'
        + 'bbf-qos-cls:filter-method' {
    description
      "The QoS policy framework allows to configure criteria to be
       applied to frames. The basic method allows to specify simple
       'in-line' classifiers. Here this is extended with a more 
       advanced classification method.";


    case by-reference {
      description
        "The classifier criteria are configured in a separate list.";

      list filter {
        key "name";

        leaf name {
          type bbf-yang:string-ascii64;
          description
            "Name of the filter.";
        }

        description
          "Filters to be matched.";
        uses filter-entry-ref;
      }
    }
  }
}
