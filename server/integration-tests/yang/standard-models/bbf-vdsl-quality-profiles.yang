submodule bbf-vdsl-quality-profiles {
  yang-version 1.1;

  belongs-to bbf-vdsl {
    prefix bbf-vdsl;
  }

  import bbf-yang-types {
    prefix bbf-yang;
  }

  include bbf-vdsl-base-body;
  include bbf-vdsl-noise-margin-profile-body;
  include bbf-vdsl-impulse-noise-protection-delay-profile-body;
  include bbf-vdsl-virtual-noise-profile-body;
  include bbf-vdsl-sos-profile-body;
  include bbf-vdsl-impulse-noise-monitoring-profile-body;
  include bbf-vdsl-re-initialization-policy-profile-body;
  include bbf-vdsl-vectoring-profile-body;
  include bbf-vdsl-data-gathering-profile-body;

  include bbf-vdsl-base;

  organization
    "Broadband Forum <https://www.broadband-forum.org>
     Common YANG Work Area";

  contact
    "Comments or questions about this Broadband Forum YANG module
     should be directed to <mailto:help@broadband-forum.org>.

     Editor:      Ken Kerpez, ASSIA, Inc.
                  <mailto:kkerpez@assia-inc.com>

     Editor:      Joey Boyd, ADTRAN
                  <mailto:joey.boyd@adtran.com>

     WA Director: Sven Ooghe, Nokia
                  <mailto:sven.ooghe@nokia.com>

     WA Director: Joey Boyd, ADTRAN
                  <mailto:joey.boyd@adtran.com>";

  description
    "This submodule contains a collection of YANG definitions for
     managing VDSL quality profiles.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c2; see
     the TR itself for full legal notices.";

  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef noise-margin-profile-ref {
    type leafref {
      path '/bbf-vdsl:vdsl/bbf-vdsl:quality/bbf-vdsl:noise-margin-'
         + 'profile/bbf-vdsl:name';
    }
    description
      "Noise Margin Profile identifier.";
  }

  typedef impulse-noise-protection-delay-profile-ref {
    type leafref {
      path '/bbf-vdsl:vdsl/bbf-vdsl:quality/bbf-vdsl:impulse-noise-'
         + 'protection-delay-profile/bbf-vdsl:name';
    }
    description
      "INP-Delay Profile identifier.";
  }

  // 5.7 DSL Quality Management related profiles

  augment '/bbf-vdsl:vdsl/bbf-vdsl:quality' {
    description
      "5.7 DSL Quality Management related profiles.";

    list noise-margin-profile {
      key "name";
      description
        "Noise Margin Profile.";

      leaf name {
        type bbf-yang:string-ascii64;
        description
          "Noise Margin Profile identifier.";
      }

      container downstream {
        description
          "Downstream Noise Margin Profile.";
        uses noise-margin-profile-downstream;
      }
      container upstream {
        description
          "Upstream Noise Margin Profile.";
        uses noise-margin-profile-upstream;
      }
    }

    list impulse-noise-protection-delay-profile {
      key "name";
      description
        "INP-Delay Profile.";

      leaf name {
        type bbf-yang:string-ascii64;
        description
          "INP-Delay Profile identifier.";
      }

      container downstream {
        description
          "Downstream INP-Delay Profile.";
        uses impulse-noise-protection-delay-profile;
        uses impulse-noise-protection-delay-profile-downstream;
      }
      container upstream {
        description
          "Upstream INP-Delay Profile.";
        uses impulse-noise-protection-delay-profile;
        uses impulse-noise-protection-delay-profile-upstream;
      }
    }

    list virtual-noise-profile {
      if-feature "virtual-noise";
      key "name";
      description
        "Virtual Noise Profile.";

      leaf name {
        type bbf-yang:string-ascii64;
        description
          "Virtual Noise Profile identifier.";
      }

      container downstream {
        description
          "Downstream Virtual Noise Profile.";
        uses virtual-noise-profile;
      }
      container upstream {
        description
          "Upstream Virtual Noise Profile.";
        uses virtual-noise-profile-upstream;
      }
    }

    list sos-profile {
      if-feature "sos";
      key "name";
      description
        "SOS Profile.";

      leaf name {
        type bbf-yang:string-ascii64;
        description
          "SOS Profile identifier.";
      }

      container downstream {
        uses sos-profile;
        description
          "Downstream SOS Profile.";
      }
      container upstream {
        uses sos-profile;
        description
          "Upstream SOS Profile.";
      }
    }

    list impulse-noise-monitoring-profile {
      if-feature "impulse-noise-monitoring";
      key "name";
      description
        "INM Profile.";

      leaf name {
        type bbf-yang:string-ascii64;
        description
          "INM Profile identifier.";
      }

      container downstream {
        description
          "Downstream INM Profile.";
        uses impulse-noise-monitoring-profile;
      }
      container upstream {
        description
          "Upstream INM Profile.";
        uses impulse-noise-monitoring-profile;
      }
    }

    list re-initialization-policy-profile {
      if-feature "re-initialization-policy";
      key "name";
      description
        "Re-Initialization Policy Profile.";

      leaf name {
        type bbf-yang:string-ascii64;
        description
          "Re-Initialization Policy Profile identifier.";
      }

      container downstream {
        description
          "Downstream Re-Initialization Policy Profile.";
        uses re-initialization-policy-profile;
      }
      container upstream {
        description
          "Upstream Re-Initialization Policy Profile.";
        uses re-initialization-policy-profile;
      }
    }

    list vectoring-profile {
      if-feature "vectoring";
      key "name";
      description
        "Vectoring Profile.";

      leaf name {
        type bbf-yang:string-ascii64;
        description
          "Vectoring Profile identifier.";
      }

      uses vectoring-profile-non-directional;

      container downstream {
        description
          "Downstream Vectoring Profile.";
        uses vectoring-profile;
      }
      container upstream {
        description
          "Upstream Vectoring Profile.";
        uses vectoring-profile;
      }
    }

    list data-gathering-profile {
      if-feature "data-gathering";
      key "name";
      description
        "Data Gathering Profile.";

      leaf name {
        type bbf-yang:string-ascii64;
        description
          "Data Gathering Profile identifier.";
      }

      container vtu {
        description
          "VTU Data Gathering Profile.";
        uses data-gathering-profile;
      }
    }
  }
}
