module test-when {
  yang-version 1.1;
  namespace "http://example.com/netopeer2-integration-tests/test-when";
  prefix test-when;

  description
    "Module that is used to test when statements";

  container test-when {
    leaf when-check {
      type boolean;
    }

    leaf gated-data {
      when "../when-check = 'true'";
      type uint16;
    }
  }
}
