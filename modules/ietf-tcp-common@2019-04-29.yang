module ietf-tcp-common {
     yang-version 1.1;
     namespace "urn:ietf:params:xml:ns:yang:ietf-tcp-common";
     prefix tcpcmn;

     organization
       "IETF NETCONF (Network Configuration) Working Group and the
        IETF TCP Maintenance and Minor Extensions (TCPM) Working Group";

     contact
       "WG Web:   <http://datatracker.ietf.org/wg/netconf/>
                  <http://datatracker.ietf.org/wg/tcpm/>
        WG List:  <mailto:netconf@ietf.org>
                  <mailto:tcpm@ietf.org>
        Authors:  Kent Watsen <mailto:kent+ietf@watsen.net>
                  Michael Scharf
                  <mailto:michael.scharf@hs-esslingen.de>";

     description
       "This module defines reusable groupings for TCP commons that
        can be used as a basis for specific TCP common instances.

        Copyright (c) 2019 IETF Trust and the persons identified
        as authors of the code. All rights reserved.

        Redistribution and use in source and binary forms, with
        or without modification, is permitted pursuant to, and
        subject to the license terms contained in, the Simplified
        BSD License set forth in Section 4.c of the IETF Trust's
        Legal Provisions Relating to IETF Documents
        (https://trustee.ietf.org/license-info).

        This version of this YANG module is part of RFC XXXX
        (https://www.rfc-editor.org/info/rfcXXXX); see the RFC
        itself for full legal notices.;
        The key words 'MUST', 'MUST NOT', 'REQUIRED', 'SHALL',
        'SHALL NOT', 'SHOULD', 'SHOULD NOT', 'RECOMMENDED',
        'NOT RECOMMENDED', 'MAY', and 'OPTIONAL' in this document
        are to be interpreted as described in BCP 14 (RFC 2119)
        (RFC 8174) when, and only when, they appear in all
        capitals, as shown here.";

     revision 2019-04-29 {
       description
         "Initial version";
       reference
         "RFC XXXX: YANG Groupings for TCP Clients and TCP Servers";
     }

     // Groupings

     grouping tcp-common-grouping {
       description
         "A reusable grouping for configuring TCP parameters common
          to TCP connections as well as the operating system as a
          whole.";
       container keepalives {
         presence "Indicates that keepalives are enabled.";
         description
           "Configures the keep-alive policy, to proactively test the
            aliveness of the TCP peer.  An unresponsive TCP peer is
            dropped after approximately (idle-time * 60) + (max-probes
            * probe-interval) seconds.";
         leaf idle-time {
           type uint16 {
             range "1..max";
           }
           units "seconds";
           mandatory true;
           description
             "Sets the amount of time after which if no data has been
              received from the TCP peer, a TCP-level probe message
              will be sent to test the aliveness of the TCP peer.";
         }
         leaf max-probes {
           type uint16 {
             range "1..max";
           }
           mandatory true;
           description
             "Sets the maximum number of sequential keep-alive probes
              that can fail to obtain a response from the TCP peer
              before assuming the TCP peer is no longer alive.";
         }
         leaf probe-interval {
           type uint16 {
             range "1..max";
           }
           units "seconds";
           mandatory true;
           description
             "Sets the time interval between failed probes.";
         }
       } // container keepalives
     } // grouping tcp-common-grouping


     grouping tcp-connection-grouping {
       description
         "A reusable grouping for configuring TCP parameters common
          to TCP connections.";
        uses tcp-common-grouping;
     }

   /*
     The following is for a future bis...
     This comment is here now so as support discussion with TCPM.
     This comment will be removed before publication.

     Should future system-level parameters be defined as a
     grouping or a container?

     grouping tcp-system-grouping {
       description
         "A reusable grouping for configuring TCP parameters common
          to the operating system as a whole.";

       // currently just a placeholder
     }
   */

   }
