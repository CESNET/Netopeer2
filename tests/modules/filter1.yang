module filter1 {
  namespace urn:f1;
  prefix f1;

  import ietf-inet-types {
    prefix "inet";
  }

  import filter1-imp {
    prefix f1i;
  }

  container top {
    container devices {
      container desktops {
        list desktop {
          key "name";
          leaf name {
            type string;
          }
          leaf address {
            type inet:ip-address;
          }
        }
      }
      container servers {
        list server {
          key "name";
          leaf name {
            type string;
          }
          leaf address {
            type inet:ip-address;
          }
          leaf port {
            type inet:port-number;
          }
          container attributes {
            leaf attr1 {
              type string;
            }
          }
        }
      }
    }

    list some-list {
      key "k";
      leaf k {
        type string;
      }
      leaf val {
        type identityref {
          base f1i:ident-base;
        }
      }
    }
  }
}
