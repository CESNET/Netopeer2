module notif2 {
  yang-version 1.1;
  namespace "urn:n2";
  prefix "n2";

  container devices {
    list device {
     key "name";
     leaf name {
          type string;
      }
      notification power-on {
        leaf boot-time {
          type uint32;
        }
      }
    }
  }
}
