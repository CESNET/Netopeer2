module sm {
    yang-version 1.1;
    namespace "urn:sm";
    prefix "sm";

    import ietf-yang-schema-mount {
        prefix yangmnt;
    }

    container root {
        yangmnt:mount-point "root";
    }
    container root2 {
        yangmnt:mount-point "root";
    }
    container root3 {
        list ls {
            key name;
            leaf name {
                type string;
            }
            yangmnt:mount-point "mnt-root";
        }
    }
    leaf target {
        type string;
    }
}
